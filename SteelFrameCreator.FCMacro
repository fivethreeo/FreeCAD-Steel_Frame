import os, sys
sys.path.append(os.path.dirname(__file__))

import SteelFrameCreator as sfc

a=FreeCAD.ActiveDocument.addObject("Part::FeaturePython","Steel_Frame")
sfc.Steel_Frame(a)
a.ViewObject.Proxy    =    0

App.ActiveDocument.recompute()
