import os, sys
sys.path.append(os.path.dirname(__file__))

from importlib import reload
from PySide import QtGui, QtCore
import FreeCADGui, Arch, Draft
import funcPanelizer as fP

#Reload in debug mode
reload(fP.tools)
reload(fP.panelize)
reload(fP.pdfTools)

__Name__ = 'Panelize Steel Frame'
__Comment__ = ''
__Author__ = ''
__Version__ = ''
__Date__ = ''
__License__ = ''
__Web__ = ''
__Wiki__ = ''
__Icon__ = ''
__Help__ = ''
__Status__ = 'Pre-alpha'
__Requires__ = ''
__Communication__ = ''
__Files__ = ''


class DialogPanelizer():
    """
    
    """
    def __init__(self):     
        self.form = FreeCADGui.PySideUic.loadUi(fP.tools.pathUI)        
        self.form.cancel.clicked.connect(self.cancel)
        self.form.changeFrame.clicked.connect(self.updateFrameSelection)
        self.form.selectFace.clicked.connect(self.getSelectedFace)
        self.form.panelize.clicked.connect(self.panelize)
        self.form.updateMaterialsButton.clicked.connect(self.fillMaterialsCombo)        
        self.form.reusePieces.setChecked(True)      
        self.form.infoFace.setText("")
        self.form.directoryPdf.setProperty("fileName",fP.tools.fileDir)
        ##Panels
        self.model = QtGui.QStandardItemModel()
        self.model.setHorizontalHeaderLabels(["Length","Height"])
        self.form.sizesList.setModel(self.model)
        self.form.sizesList.setUniformRowHeights(True)
        self.form.sizesList.setItemDelegate(PanelSizesDelegate())
        QtCore.QObject.connect(self.form.addButton,QtCore.SIGNAL("pressed()"),self.addPanelSize)
        QtCore.QObject.connect(self.form.delButton,QtCore.SIGNAL("pressed()"),self.delPanelSize)
        self.addPanelSize(1219,2743)
        self.addPanelSize(2743,1219)
        self.addPanelSize(1219,2438)        
        self.addPanelSize(2438,1219)        
        ###
        self.existingmaterials = []
        self.createDefaultMaterials()
        self.fillMaterialsCombo()       
        ##
        self.selection=Gui.Selection.getSelection()
        self.frame=None
        self.face=None
        self.flip=0
        self.rectangles=[]
        self.panelPieces=[]
        self.getSteelFrame(self.selection)

        
    #Removes standard buttons from the tasks panel
    def getStandardButtons(self):       
        return int()
    
    def cancel(self):       
        FreeCADGui.Control.closeDialog()
        
    def addPanelSize(self, length=1000, height=2000):
        item1 = QtGui.QStandardItem()       
        item2 = QtGui.QStandardItem()
        item1.setText(str(length)+" mm")
        item2.setText(str(height)+" mm")
        self.model.appendRow([item1,item2])
        
    def delPanelSize(self):
        sel = self.form.sizesList.selectedIndexes()
        if sel:
            row = sel[0].row()
            if row >= 0:
                self.model.takeRow(row)
                
    def getPanelSizes(self):
        sizes=[]        
        for row in range(self.model.rowCount()):            
            l = self.model.item(row,0).text()
            h = self.model.item(row,1).text()
            length, height=FreeCAD.Units.Quantity(l).Value,FreeCAD.Units.Quantity(h).Value
            if (length,height) not in sizes:
                sizes.append((length,height))                   
        return sizes
    
    def createDefaultMaterials(self):
        existingMaterials = []
        for obj in FreeCAD.ActiveDocument.Objects:
            if Draft.getType(obj) == "MultiMaterial" or obj.isDerivedFrom("App::MaterialObject"):
                existingMaterials.append(obj.Label)
        if "FRCC_Mat" not in existingMaterials:
            frcc=Arch.makeMaterial()
            frcc.Label="FRCC_Mat"
            frcc.Color=(0.67,0.67,0.67) 
            foam=Arch.makeMaterial()
            foam.Label="Foam_Mat"
            foam.Color=(1.0,1.0,0.75)           
            rokon=Arch.makeMultiMaterial()
            rokon.Label="ROK-ON_Mat"
            rokon.Materials=[frcc,foam,frcc]
            rokon.Names=["FRCC6","Foam","FRCC12"]
            rokon.Thicknesses=[6.0,0.0,12.0]
    
    def fillMaterialsCombo(self):
        "fills the existing multimaterials combo"       
        self.existingmaterials = []
        for obj in FreeCAD.ActiveDocument.Objects:
            if Draft.getType(obj) == "MultiMaterial" or obj.isDerivedFrom("App::MaterialObject"):
                self.existingmaterials.append(obj)
        self.form.materialCombo.clear()
        for m in self.existingmaterials:
            self.form.materialCombo.addItem(m.Label)
            
        
    def enableFormElements(self,flag):
        self.form.offsetSup.setEnabled(flag)
        self.form.offsetBottom.setEnabled(flag)
        self.form.offsetLeft.setEnabled(flag)
        self.form.offsetRight.setEnabled(flag)
        self.form.offsetWindows.setEnabled(flag)
        self.form.offsetDoors.setEnabled(flag)
        self.form.offsetJoints.setEnabled(flag)
        self.form.reusePieces.setEnabled(flag)
        self.form.panelize.setEnabled(flag)
        self.panelPieces=[] 
    
    #Get the Steel Frame    
    def getSteelFrame(self,selection):
        if len(selection)==1:
            sel=selection[0]
            #Check some attributes to ensure the selection is a Steel Frame object
            if hasattr(sel,'Windows') and hasattr(sel,'Height') and hasattr(sel,'Height') and hasattr(sel,'Gauge'):
                frameProperties="Label: "+str(sel.Label)
                frameProperties+="\nLength: "+str(sel.Length)
                frameProperties+="\nWindows: "+str(len(sel.Windows))
                self.frame=sel
                self.form.infoFrame.setText(frameProperties)
                self.form.selectFace.setEnabled(True)
            else:
                self.form.infoFrame.setText("Select one Steel Frame")
        else:
            self.form.infoFrame.setText("Select one Steel Frame")
            
    def updateFrameSelection(self):
        """
        Updates the frame selection
        """
        try:
            del self.selection
        except:
            pass
        self.enableFormElements(False)
        self.form.selectFace.setEnabled(False)
        self.form.infoFace.setText("")      
        self.selection=Gui.Selection.getSelection()
        self.getSteelFrame(self.selection)
    
    def getSelectedFace(self):
        try:
            self.face=Gui.Selection.getSelectionEx()[0].SubObjects[0] #Get the edge or face selected
            faceName=Gui.Selection.getSelectionEx()[0].SubElementNames[0]
            frameLabel=Gui.Selection.getSelection()[0].Label
        except:
            self.form.infoFace.setText("Select a face on \nthe side to panelize.")                      
        self.enableFormElements(False)
        if self.face and hasattr(self.face,'ShapeType') and frameLabel==self.frame.Label:
            if self.face.ShapeType=='Face':
                #Checks if the face orientation is the same as the Steel Frame
                vectorWidth=self.frame.Placement.Rotation.multVec(FreeCAD.Vector(0,1,0)) #Vector defining the orientation along the Width
                faceNormal=self.face.normalAt(0,0) #Normal vector
                tolerance=FreeCAD.Units.MilliMetre*1e-3
                
                if faceNormal.cross(vectorWidth).isEqual(FreeCAD.Vector(0,0,0),tolerance): #Checks collinearity between the normal vector and vectorWidth
                    self.form.infoFace.setText(faceName)
                    self.enableFormElements(True)                    
                    
                    if vectorWidth.isEqual(faceNormal,tolerance): #If the normal Vector is equal to the normal vector on the side 1
                        self.flip=1
                    else:
                        self.flip=0
                    # faceVertex=self.face.Vertexes[0].Point
                    # if abs(faceVertex.distanceToPlane(self.frame.Placement.Base,faceNormal))>self.frame.Width/2:
                        # self.flip=1                     
                    # else:
                        # self.flip=0                 
                else:
                    self.form.infoFace.setText('That\'s not a possible side')
            else:
                self.form.infoFace.setText('Select a face \non the side to panelize.')
        else:
            self.form.infoFace.setText('Select a face \non the side to panelize.')
            
    def exportPdf(self, thickness, material):
        """
        Exports the panel pieces position in pdf
        """     
        projectName = self.form.projectName.text()
        projectRevision = self.form.projectRevision.text()
        directory = self.form.directoryPdf.property("fileName")
        assemblyName=fP.tools.assemblyName(self.frame)  
        fP.pdfTools.createPdf(self.frame, self.panelPieces, self.flip, projectName, projectRevision, directory, assemblyName, thickness, material)
        
    
    def panelize(self):
        """
        Panelize the steel Frame on the selected side 
        """
        offSets={'Top': self.form.offsetSup.property("quantity").Value,
                 'Bottom': self.form.offsetBottom.property("quantity").Value,
                 'Left': self.form.offsetLeft.property("quantity").Value,
                 'Right': self.form.offsetRight.property("quantity").Value,
                 'Windows': self.form.offsetWindows.property("quantity").Value,
                 'Doors': self.form.offsetDoors.property("quantity").Value,
                 'Joints': self.form.offsetJoints.property("quantity").Value}
        self.panelSizes=self.getPanelSizes()
        if len(self.panelSizes)==0:
            FreeCAD.Console.PrintWarning("Standard Panel Sizes not provided.\n")
            return None
        
        self.rectangles=fP.tools.divideFrame(self.frame,offSets,self.flip)
        thickness = self.form.panelThickness.property("quantity").Value
        minVertSize = self.form.minVertSize.property("quantity").Value
        minHorSize = self.form.minHorSize.property("quantity").Value
        if minHorSize <= self.frame.Separation:
            FreeCAD.Console.PrintWarning("The minimum horizontal size is smaller than the stud separation size.\n")
        if offSets['Top']>0 and minVertSize <= offSets['Top']:
            FreeCAD.Console.PrintWarning("The minimum vertical size is smaller than the top offset.\n")
            
        
        if len(self.existingmaterials)>0:
            iM = self.form.materialCombo.currentIndex()
            material=self.existingmaterials[iM]
            if hasattr(material, 'Thicknesses'):            
                if thickness < sum(material.Thicknesses):
                    FreeCAD.Console.PrintWarning("The thickness is too small for the material.\n")
                    return None
        else:
            material = None

            
        reusePieces = self.form.reusePieces.isChecked()
        self.panelPieces = []
        waste = 0 
        area = 0
        for sR in self.rectangles:                 
            panelizeResult=fP.panelize.panelize([tuple(sR.vertI),(sR.Length,sR.Height)],
                            self.panelSizes, reusePieces, minHorSize, minVertSize)
            self.panelPieces.extend(fP.tools.convertToRectangle(panelizeResult[0]))
            waste += panelizeResult[1]
            area += (sR.Length * sR.Height)
        

        for r in self.panelPieces:
            panelPiece = fP.tools.drawPanel(r,self.frame,self.flip,thickness,material, self.form.panelName.text())
            setattr(r,'Label',panelPiece.Label)         
            fP.tools.groupPanelPieces(panelPiece, self.frame)
        FreeCAD.ActiveDocument.recompute()        
        
        FreeCAD.Console.PrintMessage('Waste: '+str(round(waste/1e6,2))+' m2')
        FreeCAD.Console.PrintMessage(' ,'+str(round(waste*100/area,3))+' %\n')

        #Exports the steel frame and the panel pieces to a pdf file
        if self.form.exportPdf.isChecked():
            self.exportPdf(thickness, material.Label)
        self.panelPieces = []
        self.rectangles = []
        
            
        

class PanelSizesDelegate(QtGui.QStyledItemDelegate):
    """
    The Delegate Class to create the items in the panelSizes item container
    """
    def __init__(self, parent=None, *args):
        QtGui.QStyledItemDelegate.__init__(self, parent, *args)
        
    def createEditor(self,parent,option,index):
        ui = FreeCADGui.UiLoader()
        editor = ui.createWidget("Gui::InputField")
        editor.setProperty("minimum",1)
        editor.setProperty("unit","mm")     
        editor.setSizePolicy(QtGui.QSizePolicy.Preferred,QtGui.QSizePolicy.Minimum)
        editor.setParent(parent)
        return editor
        
    


###Dialog is created as an instance of the DialogPanelizer class and put into the Tasks Panel
dialog = DialogPanelizer() 

if not FreeCAD.ActiveDocument:
    FreeCAD.Console.PrintError("No active document.\n")
else:
    if FreeCADGui.Control.activeDialog()==False:
        FreeCADGui.Control.showDialog(dialog)
    else:
        flags = QtGui.QMessageBox.StandardButton.Yes
        flags |= QtGui.QMessageBox.StandardButton.No
        cerrar = QtGui.QMessageBox.question(None,
                          "Question",
                           "There are dialogs open in the Tasks Panel.\n Do you want to close them?",
                            flags)
        if cerrar== QtGui.QMessageBox.Yes:
            FreeCADGui.Control.closeDialog()
            FreeCADGui.Control.showDialog(dialog)
        else:
            FreeCAD.Console.PrintMessage("Panelizer not executed.\n")
